Ativo DEFINITIONS AUTOMATIC TAGS ::=
BEGIN

IntList ::= SEQUENCE OF INTEGER

BoolList ::= SEQUENCE OF BOOLEAN

Interno ::= SET {
  cod INTEGER,
  oid PrintableString
}

Tipo1 ::= SEQUENCE {
  id IntList,
  nome PrintableString,
  lixo Interno
}

Tipo2 ::= SEQUENCE {
  id BoolList,
  nome PrintableString
}

Ativo ::= SEQUENCE {
  id CHOICE {
    t1 Tipo1,
    t2 Tipo2
  },
  valor INTEGER,
  data NumericString(SIZE(8)),
  horario NumericString (SIZE(6))
}
 
END
